[DOCUMENT]
MID: c8df4cbae54e405e81ad87764b262a6b
TITLE: System Concept of Operations
OPTIONS:
  ENABLE_MID: True

[GRAMMAR]
IMPORT_FROM_FILE: @sample_system_concept_of_operations_grammar

[TEXT]
MID: 5941c5c81aa74c8497b9051a7ee0856d
STATEMENT: >>>
SPDX-License-Identifier: Apache-2.0
<<<

[TEXT]
MID: 47f7749075a74956b4160114edab0f05
STATEMENT: >>>
From `SEBoK Wiki Glossary - Concept of Operations <https://sebokwiki.org/wiki/Concept_of_Operations_(ConOps)_(glossary)>`_:

    *Verbal and graphic statement, in broad outline, of an organization’s assumptions or intent in regard to an operation or series of operations.* (ISO/IEC 2011)

  Source
    ISO/IEC 2011. *Systems and software engineering - Life cycle processes - Requirements engineering*. Geneva, Switzerland: International Organization for Standardization/International Electrotechnical Commissions. ISO/IEC 29148.

  Discussion
    The concept of operations frequently is embodied in long-range strategic plans and annual operational plans. In the latter case, the concept of operations in the plan covers a series of connected operations to be carried out simultaneously or in succession. The concept is designed to give an overall picture of the organization operations.

    It provides the basis for bounding the operating space, system capabilities, interfaces and operating environment.

    See also operational concept which is slightly different.
<<<
