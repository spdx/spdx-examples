[DOCUMENT]
TITLE: SEBoK Product as System - Commodity Consumer Electronics

[TEXT]
STATEMENT: >>>
NOTE: Normative content is captured in structured, traceable StrictDoc items.

StrictDoc `[TEXT]` blocks are unstructured and hold only informative content. 
<<<

[DOCUMENT_FROM_FILE]
FILE: problem_space/sdoc/index.sdoc

[DOCUMENT_FROM_FILE]
FILE: system_concept_of_operations/sdoc/index.sdoc

[DOCUMENT_FROM_FILE]
FILE: system_validations/sdoc/index.sdoc

[DOCUMENT_FROM_FILE]
FILE: shared/interface_specifications/sdoc/index.sdoc

[DOCUMENT_FROM_FILE]
FILE: SOI/sdoc/index.sdoc
