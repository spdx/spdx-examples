[DOCUMENT]
TITLE: Problem Space Catalog

[TEXT]
STATEMENT: >>>
SPDX-License-Identifier: Apache-2.0
<<<

[TEXT]
STATEMENT: >>>
The Problem Space Catalog contains Stakeholder-level content 
(i.e., characteristics, needs and requirements) 
that describes the potential problem space under consideration for a solution. 
This problem space is likely larger than what will be addressed by a specific solution 
(e.g., product, product-line, or business).
<<<

[DOCUMENT_FROM_FILE]
FILE: ../stakeholders/sdoc/index.sdoc

[DOCUMENT_FROM_FILE]
FILE: ../personas/sdoc/index.sdoc
